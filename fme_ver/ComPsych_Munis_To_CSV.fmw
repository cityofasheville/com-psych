FME workspace ComPsych_Munis_To_CSV.fmw

Parameters:
- SourceDataset_MSSQL_ADO = munprod   # SQL Server Connection
- DestDataset_CSV2 = .   # Destination CSV (Comma Separated Value) Folder

Readers:
- MSSQL_ADO_1: MSSQL_ADO from $(SourceDataset_MSSQL_ADO)

Writers:
- CSV2_1: CSV2 to $(DestDataset_CSV2)

avl.sunlife_eligibility (reader MSSQL_ADO_1)
    attributes: Account Number integer, Account Name varchar(17), Employee ID # integer, Employee SSN# varchar(1), First Name varchar(30), Middle Initial varchar(1), Last Name varchar(30), Home Address Line #1 varchar(64), Home Address Line #2 varchar(64), Home City varchar(25), Home State / Providence varchar(2), Home Zip / Postal Code varchar(10), Home Country varchar(3), Home (or Primary) Phone # varchar(30), Gender varchar(1), Date of Birth nvarchar(4000), Primary Language varchar(1), Work Address ID varchar(1), Work Address Line #1 varchar(1), Work Address Line #2 varchar(1), Work City varchar(1), Work State / Providence varchar(2), Work Zip varchar(1), Work Country varchar(1), Work Phone # varchar(1), Work Phone Extension varchar(1), Business Unit varchar(50), Organization varchar(50), Exempt Status varchar(30), Personnel Status varchar(1),
      Employee Group #3 varchar(1), Employee Group #4 varchar(1), Employee Group #5 varchar(1), Employee Group #6 varchar(1), Employee Group #7 varchar(1), Employee Group #8 varchar(1), Full Time / Part Time Status varchar(1), Hire Date nvarchar(4000), Adjusted Employment Date nvarchar(4000), Anniversary Date varchar(1), Termination Date varchar(1), Hours Worked in the Previous 12 Months numeric(38,2), Key Employee varchar(1), Job Title varchar(30), Work E-mail Address varchar(256), Scheduled Hours per Week numeric(10,2), Scheduled # of Days per Week numeric(10,2), Additional Letter Recipient E-mail varchar(1), Spouse Employed  varchar(1), Spouse Employee ID varchar(1), Employer Contact 1 IDS integer, STD Earnings varchar(1), STD Eligibility Date varchar(1), LTD Eligibility Date varchar(1), Employer Contact 2 IDS varchar(1), Employer Contact 3 IDS varchar(1), Employer Contact 4 IDS varchar(1), Employer Contact 5 IDS varchar(1), Employer Contact 6 IDS varchar(1), Employer Contact 7 IDS varchar(1),
      Employer Contact 8 IDS varchar(1), Employer Contact 9 IDS varchar(1), Employer Contact 10 IDS varchar(1)
    -> avl.sunlife_eligibility (writer CSV2_1)
avl.sunlife_eligibility (writer CSV2_1)
    attributes: Account Number string, Account Name string, Employee ID # string, Employee SSN# string, First Name string, Middle Initial string, Last Name string, Home Address Line #1 string, Home Address Line #2 string, Home City string, Home State / Providence string, Home Zip / Postal Code string, Home Country string, Home (or Primary) Phone # string, Gender string, Date of Birth string, Primary Language string, Work Address ID string, Work Address Line #1 string, Work Address Line #2 string, Work City string, Work State / Providence string, Work Zip string, Work Country string, Work Phone # string, Work Phone Extension string, Business Unit string, Organization string, Exempt Status string, Personnel Status string,
      Employee Group #3 string, Employee Group #4 string, Employee Group #5 string, Employee Group #6 string, Employee Group #7 string, Employee Group #8 string, Full Time / Part Time Status string, Hire Date string, Adjusted Employment Date string, Anniversary Date string, Termination Date string, Hours Worked in the Previous 12 Months string, Key Employee string, Job Title string, Work E-mail Address string, Scheduled Hours per Week string, Scheduled # of Days per Week string, Additional Letter Recipient E-mail string, Spouse Employed  string, Spouse Employee ID string, Employer Contact 1 IDS string, STD Earnings string, STD Eligibility Date string, LTD Eligibility Date string, Employer Contact 2 IDS string, Employer Contact 3 IDS string, Employer Contact 4 IDS string, Employer Contact 5 IDS string, Employer Contact 6 IDS string, Employer Contact 7 IDS string,
      Employer Contact 8 IDS string, Employer Contact 9 IDS string, Employer Contact 10 IDS string
